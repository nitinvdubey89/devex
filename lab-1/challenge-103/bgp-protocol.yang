module bgp-protocol {
  namespace "http://devnetexperttraining.com/bgp-protocol";
  prefix bgp;

// Requirement A
  import ietf-inet-types {
    prefix inet;
  }


  container bgp-protocol {
    // Requirement B
    typedef as-number {
      type uint32 {
        range "64512..65534 | 4200000000..4294967294";
      }
    }
    leaf router-id {
      type inet:ipv4-address;
      mandatory true;
    }
    leaf local-as {
      type as-number;
      mandatory true;
    }
    // Requirement C
    list vrf {
      key name;
      leaf name {
        type string;
        mandatory true;
      }
    }

    container neighbors {

      list neighbor {
        key address;

        leaf address {
          type inet:ipv4-address;
          mandatory true;
        }

        leaf remote-as {
          type as-number;
          mandatory true;
        }

        leaf vrf {
          type leafref {
            path "../../../vrf/name";
          }
        }

        leaf admin-state {
          type enumeration {
            enum ENABLED {
              value 1;
            }
            enum DISABLED {
              value 2;
            }
          }
          mandatory true;
        }

        leaf operational-state {
          config false;
          type enumeration {
            enum UP;
            enum DOWN;
          }
        }

        choice password-or-gtsm {
          when "remote-as != ../../local-as";
          case password {
            leaf password {
              type string;
            }
          }
          case gtsm {
            leaf ttl {
              type uint8;
            }
          }
        }
      }

      // Requirement D
      //

      // Requirement E
      //

      // Requirement F
      //

      // Requirement G
      //

    }
  }
}
