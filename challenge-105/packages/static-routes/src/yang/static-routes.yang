module static-routes {

  namespace "http://example.com/static-routes";
  prefix static-routes;

  import ietf-inet-types {
    prefix inet;
  }
  import tailf-common {
    prefix tailf;
  }
  import tailf-ncs {
    prefix ncs;
  }

  description
    "Challenge 105";

  revision 2022-10-02 {
    description
      "Initial revision.";
  }

  list static-routes {
    description "This is an RFS skeleton service";

    key name;
    leaf name {
      tailf:info "Unique service id";
      tailf:cli-allow-range;
      type string;
    }

    uses ncs:service-data;
    ncs:servicepoint static-routes-servicepoint;

    leaf-list device {
      type leafref {
        path "/ncs:devices/ncs:device/ncs:name";
      }
    }

    //Requirement A

    //
  }
}
